;; osnap-presets.lsp - Running object snap presets
;; Commands: OSEND / OSMID / OSINT / OSALL / OSNONE
;; Usage: APPLOAD -> run the preset you need before picking
(defun c:OSEND ( )
  (setvar "OSMODE" 1)
  (princ "\nOsnap: ENDpoint only.")
  (princ)
)
(defun c:OSMID ( )
  (setvar "OSMODE" 3)
  (princ "\nOsnap: ENDpoint + MIDpoint.")
  (princ)
)
(defun c:OSINT ( )
  (setvar "OSMODE" 33)
  (princ "\nOsnap: ENDpoint + INTersection.")
  (princ)
)
(defun c:OSALL ( )
  (setvar "OSMODE" 767)
  (princ "\nOsnap: all running modes.")
  (princ)
)
(defun c:OSNONE ( )
  (setvar "OSMODE" 0)
  (princ "\nOsnap: off.")
  (princ)
)
